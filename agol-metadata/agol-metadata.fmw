FME workspace agol-metadata.fmw

Parameters:
- metadata_file =   # metadata file
- username =
- password =
- item =
- endpoint = https://www.arcgis.com/sharing/rest

Note: Auteur: Willy Tadema / Datum: 20 juli 2018 / Omschrijving: / Workspace om te demonstreren hoe je metadata van een item in ArcGIS Online kunt bijwerken via de REST API / Published parameters: / metadata_file - pad naar het XML-bestand met de nieuwe metadata / username - ArcGIS Online gebruikersnaam / password - ArcGIS Online wachtwoord / item - unieke identifier voor het item dat bijgewerkt moet worden / Private parameters: / endpoint - URL van de ArcGIS REST API
Creator
    GEOMTYPE = Geometry Object
    NUM = 1
    CREATED -> HTTPCaller
HTTPCaller_2_Output: Inspector
HTTPCaller_2__Rejected_: Inspector

Bookmark: Token opvragen
HTTPCaller
    CONNECTION_TIMEOUT_LENGTH = 60
    ERROR_ATTR = _error
    FOLLOW_REDIRECTS = Yes
    HTTP_METHOD = POST
    MULTIPARTS = username StringUpload SOURCE_EXPRESSION;$(username);MIME_TYPE;text/plain;FME_CONTROLLER_QUERY_FILE;transformers\dependencies\http\StringUpload.fme password StringUpload SOURCE_EXPRESSION;$(password);MIME_TYPE;text/plain;FME_CONTROLLER_QUERY_FILE;transformers\dependencies\http\StringUpload.fme referer StringUpload SOURCE_EXPRESSION;http://www.arcgis.com;MIME_TYPE;text/plain;FME_CONTROLLER_QUERY_FILE;transformers\dependencies\http\StringUpload.fme f StringUpload SOURCE_EXPRESSION;json;MIME_TYPE;text/plain;FME_CONTROLLER_QUERY_FILE;transformers\dependencies\http\StringUpload.fme
    SAVE_FILE = Attribute
    STATUS_CODE_ATTR = _http_status_code
    TARGET_ATTR = _response_body
    TARGET_ATTR_ENCODING = auto-detect
    TARGET_URL = $(endpoint)/generateToken
    TRANSFER_TIMEOUT_LENGTH = 90
    UPLOAD_TYPE = Multipart / Form Data
    USE_COOKIES = No
    VERIFY_SSL_CERTIFICATES = No
    -> JSONFlattener
JSONFlattener
    ERROR_LIST_ATTR = _json_error
    JSON_DOCUMENT = @Value(_response_body)
    NEW_ATTRIBUTES = token
    READ_FROM_FILE = NO
    RECURSIVE = Yes
    -> AttributeKeeper
AttributeKeeper
    KEEP_ATTRS = token
    -> HTTPCaller_2

Bookmark: Metadata bijwerken
HTTPCaller_2
    CONNECTION_TIMEOUT_LENGTH = 60
    ERROR_ATTR = _error
    FOLLOW_REDIRECTS = Yes
    HTTP_METHOD = POST
    MULTIPARTS = overwrite StringUpload SOURCE_EXPRESSION;true;MIME_TYPE;text/plain;FME_CONTROLLER_QUERY_FILE;transformers\dependencies\http\StringUpload.fme token StringUpload SOURCE_EXPRESSION;@Value(token);MIME_TYPE;text/plain;FME_CONTROLLER_QUERY_FILE;transformers\dependencies\http\StringUpload.fme f StringUpload SOURCE_EXPRESSION;json;MIME_TYPE;text/plain;FME_CONTROLLER_QUERY_FILE;transformers\dependencies\http\StringUpload.fme metadata FileUpload SOURCE_FILE;$(metadata_file);MIME_TYPE;text/xml;FME_CONTROLLER_QUERY_FILE;transformers\dependencies\http\FileUpload.fme
    SAVE_FILE = Attribute
    STATUS_CODE_ATTR = _http_status_code
    TARGET_ATTR = _response_body
    TARGET_ATTR_ENCODING = auto-detect
    TARGET_URL = $(endpoint)/content/users/$(username)/items/$(item)/update
    TRANSFER_TIMEOUT_LENGTH = 90
    UPLOAD_TYPE = Multipart / Form Data
    USE_COOKIES = No
    VERIFY_SSL_CERTIFICATES = No
    -> HTTPCaller_2_Output
    <REJECTED> -> HTTPCaller_2__Rejected_
